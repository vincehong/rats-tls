-- RATS-TLS ASN.1 syntax
CCC-RA-TLS {
    -- To be replaced by an oid of CCC.
    iso(1) member-body(2) us(840) intel(113741)
} DEFINITIONS ::= BEGIN

    -- To be replaced by an oid of CCC.
    oid-ccc  OBJECT IDENTIFIER  ::= {iso(1) member-body(2) us(840) intel(113741)}

    CCC-RA-TLS-Certificate-Extension ::= SEQUENCE {
        id-ccc-ra-tls ID-CCC-RA-TLS,
        version  CCC-RA-TLS-Certificate-Extension-Version (1),
        evidence CCC-RA-TLS-Certificate-Extension-Evidence,
        endorsement CCC-RA-TLS-Certificate-Extension-endorsement
    }

    -- oid of other TEE vendors are to be added.
    ID-CCC-RA-TLS ::= OBJECT IDENTIFIER (id-sgx-local-report |
                                        id-sgx-epid |
                                        id-sgx-ecdsa |
                                        id-tdx-ecdsa |
                                        id-tdx-local-report)


    id-sgx-local-report OBJECT IDENTIFIER ::= {
        oid-ccc  1
    }
    
    id-sgx-epid OBJECT IDENTIFIER ::= {
        oid-ccc  2
    }
    
    id-sgx-ecdsa OBJECT IDENTIFIER ::= {
        oid-ccc  3
    }
    
    id-tdx-ecdsa OBJECT IDENTIFIER ::= {
        oid-ccc  4
    }
    
    id-tdx-local-report OBJECT IDENTIFIER ::= {
        oid-ccc  5
    }   
    
    CCC-RA-TLS-Certificate-Extension-Version ::= INTEGER (1..255)

    CCC-RA-TLS-Certificate-Extension-Evidence ::= CHOICE {
            sgxEpid        [0] EXPLICIT CCC-RA-TLS-Certificate-Extension-Evidence-SGX-EPID,
            sgxEcdsa       [1] EXPLICIT CCC-RA-TLS-Certificate-Extension-Evidence-SGX-ECDSA,
            sgxLocalReport [2] EXPLICIT CCC-RA-TLS-Certificate-Extension-Evidence-SGX-LOCAL-REPORT,
            tdxEcdsa       [3] EXPLICIT CCC-RA-TLS-Certificate-Extension-Evidence-TDX-ECDSA,
            tdxLocalReport [4] EXPLICIT CCC-RA-TLS-Certificate-Extension-Evidence-TDX-LOCAL-REPORT
        }
 
    CCC-RA-TLS-Certificate-Extension-Evidence-SGX-EPID ::= SEQUENCE {
        content OCTET STRING
    }

    CCC-RA-TLS-Certificate-Extension-Evidence-SGX-ECDSA ::= SEQUENCE {
        content OCTET STRING
    }

    CCC-RA-TLS-Certificate-Extension-Evidence-SGX-LOCAL-REPORT ::= SEQUENCE {
        content OCTET STRING
    }

    CCC-RA-TLS-Certificate-Extension-Evidence-TDX-ECDSA ::= SEQUENCE {
        content OCTET STRING
    }

    CCC-RA-TLS-Certificate-Extension-Evidence-TDX-LOCAL-REPORT ::= SEQUENCE {
        content OCTET STRING
    }

    CCC-RA-TLS-Certificate-Extension-endorsement  ::= SEQUENCE {
        content OCTET STRING
    }

END
